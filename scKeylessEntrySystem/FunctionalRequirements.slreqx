# Functional Requirements
Captures the functional requirements of the keyless entry system

## #1: Should unlock door (Functional)
The door should unlock when the key is detected within 0.5m of the door handle and the user grabs the door handle.

## #2: Should lock door (Functional)
The door should lock when the key is detected within 0.5m of the door handle and the user touches the top of the door handle.

## #3: Welcome lights (Functional)
The lights should trun on inside when the key is detected wihtin 0.5m of the car.

## #4: Automatically turn off headlights (Functional)
The headlights should turn off after the car is turned off

## #5: Flash headlights on lock (Functional)
The headlights should flash when the car is locked.

## #6: Emit sound when car unlocked (Functional)
The car should emit a sound when the car is unlocked

## #7: Emit sound when car locked (Functional)
The car should emit a sound when the car is locked

## #8: Emit sound when car is on but not key detected (Functional)
The car should emit a sound when the car is on and the key is no longer inside the vehicle.

## #9: Engine start with push button (Functional)
The engine should start when the key is inside of the car and the push button is pressed. Additionally the brake pedal must also be depressed.

## #10: Engine stop with push button (Functional)
The engine should stop when the key is inside of the car and the push button is pressed. Additionally, the car must be in "Park".
